MyModule DEFINITIONS ::=
BEGIN

MyTypes ::= SEQUENCE {
    myObjectId   OBJECT IDENTIFIER,
    mySeqOf      SEQUENCE OF MyInt,
    myBitString  BIT STRING {
                        muxToken(0), 
                        modemToken(1)
                 }
}

ColorType ::= ENUMERATED
       {
          red      (0),
          white    (1),
          blue     (2)
       }

Animals ::= ENUMERATED
       {
          dog     (0),
          cat     (1),
          horse   (2)
       }

MyInt ::= INTEGER (0..65535)

END
